FME workspace resetPassword-FMEServerSharedEval.fmw

Parameters:
- user_account = donatsafe   # User Account
- Evaluation_Server = https://fmeserver-eval-safe-software.fmecloud.com   # https Evaluation Server URL

Writers:
- HTML_1: HTML to /Users/dcm/Dropbox (Safe Software Inc.)/DonStuffMac/DonStuff/DemoData/FME2017/FMEServerEvaluation/FMEServerEvalReport.html

Creator
    NUM = 1
    GEOMTYPE = Geometry Object
    CREATED -> HTTPCaller_2
HTML (writer HTML_1)
    attributes: html_content buffer
HTTPCaller__Rejected_: Logger
    MAXCOORDS = 20
    MAXFEATS = 20
    MESSAGE = Feature is:

Bookmark: Retrieve User Info
Note: Get User Account Info
HTTPCaller_2
    AUTH_NAMED_CONNECTION = donsuper FME Server Eval Machine
    STATUS_CODE_ATTR = _http_status_code
    TARGET_URL = $(Evaluation_Server)/fmerest/v3/security/accounts/$(user_account)
    AUTH_METHOD = Web Connection
    SAVE_FILE = Attribute
    TARGET_ATTR = json_user_info
    HTTP_METHOD = GET
    CONNECTION_TIMEOUT_LENGTH = 60
    TARGET_ATTR_ENCODING = auto-detect
    TRANSFER_TIMEOUT_LENGTH = 90
    ERROR_ATTR = _error
    USE_COOKIES = No
    FOLLOW_REDIRECTS = Yes
    VERIFY_SSL_CERTIFICATES = Yes
    RESPONSE_HEADER_LIST_ATTR = _headers
    -> JSONFlattener
    <Rejected> -> JSONFlattener_2
JSONFlattener
    JSON_DOCUMENT = @Value(json_user_info)
    ERROR_LIST_ATTR = _json_error
    NEW_ATTRIBUTES = email enabled fullName name type roles password
    RECURSIVE = No
    -> StringReplacer

Bookmark: Invalid user Name or Couldn't connect to Server.
JSONFlattener_2
    JSON_DOCUMENT = @Value(json_user_info)
    ERROR_LIST_ATTR = _json_error
    NEW_ATTRIBUTES = message
    RECURSIVE = Yes
    -> Error_Message.
    <REJECTED> -> JSONFlattener_2__Rejected_
JSONFlattener_2__Rejected_: Logger
    MAXCOORDS = 20
    MAXFEATS = 20
    MESSAGE = Feature is:
Note: create webpage
Error_Message.: AttributeCreator
    ATTR_TABLE:
      SET_TO html_content = <!DOCTYPE html PUBLIC "-//W3C//DTD XHTML 1.0 Transitional//EN" "http://www.w3.org/TR/xhtml1/DTD/xhtml1-transitional.dtd">
        <html xmlns="http://www.w3.org/1999/xhtml">
        <title>We'd like to give you a 60-Day FME Server Trial</title>
        <head>
        <meta http-equiv="Content-Type" content="text/html; charset=UTF-8">
        <meta name="viewport" content="initial-scale=1.0">
        <!-- So that mobile webkit will display zoomed in -->
        <meta name="format-detection" content="telephone=no">
        <!-- disable auto telephone linking in iOS -->
        <style type="text/css">
        /* Resets: see reset.css for details */


        .ReadMsgBody {
        	width: 100%;
        	background-color: #eeeeee;
        }
        .ExternalClass {
        	width: 100%;
        	background-color: #eeeeee;
        }
        .ExternalClass, .ExternalClass p, .ExternalClass span, .ExternalClass font, .ExternalClass td, .ExternalClass div {
        	line-height: 100%;
        }
        body {
        	-webkit-text-size-adjust: none;
        	-ms-text-size-adjust: none;
        }
        body {
        	margin: 0;
        	padding: 0;
        }
        table {
        	border-spacing: 0;
        }
        table td {
        	border-collapse: collapse;
        }
        .yshortcuts a {
        	border-bottom: none !important;
        }
        ul {
        	list-style-type: disc;
        	padding-left: 30px;
        }
        li {
        	list-style-type: inherit;
        	padding-left: 0px;
        	color: #4b4b4b;
        }

        h1 {
        	font-size:22px; line-height: 22px;
        }

        /* Constrain email width for small screens */
        @media screen and (max-width: 900px) {
        table[class="container"] {
        	width: 95% !important;
        }
        }

        /* Give content more room on mobile */
        @media screen and (max-width: 900px) {
        td[class="container-padding"] {
        	padding-left: 12px !important;
        	padding-right: 12px !important;
        }
        }


        /* Force columns into rows */
            @media only screen and (max-width : 900px) {
        /* force container columns to (horizontal) blocks */
        td[class="force-col"] {
        	display: block;
        	padding-right: 0 !important;/*display: table-footer-group;*/
        }
        table[class="col-2"] {
        	/* unset table align="left/right" */
        	float: none !important;
        	width: 100% !important;
        	/* change left/right padding and margins to top/bottom ones */
        	margin-bottom: 12px;
        	padding-bottom: 12px;
          /*border-bottom: 1px solid #A3ABAD;*/
          display: table-header-group;
        }
        /* removes bottom border for last column/row*/
        table[id="last-col-2"] {
        	border-bottom: none !important;
        	margin-bottom: 0px;
        }
        /* Puts images on top*/
        img[class="col-2-img"] {
        	margin-left: 0px;
        	max-width: 900px;
        }
        </style>
        </head>
        <body style="margin:0; padding:10px 0px 0px 0px;" bgcolor="#eeeeee" leftmargin="0" topmargin="0" marginwidth="0" marginheight="0">
        <!-- 100% wrapper (grey background) -->
        <table border="0" width="88%" height="100%" cellpadding="0" cellspacing="0" bgcolor="#eeeeee">
          <tbody>
            <tr>
              <td align="center" valign="top" bgcolor="#eeeeee" style="background-color: #eeeeee;"><!-- 900px container (white background) -->

                <table border="0" width="900" cellpadding="0" cellspacing="0" class="container" bgcolor="#eeeeee">
                  <tbody>
                    <!--ONE COLUMN-->
                    <tr>
                      <td align="center" class="container-padding" bgcolor="#eeeeee" style="background-color: #eeeeee; padding-top:5px; padding-bottom:15px; padding-left: 30px; padding-right: 30px; font-size: 16px; line-height: 20px; font-family:Arial, sans-serif; color: #4b4b4b;"><a href="http://www.safe.com/fme/fme-server/?utm_source=safe&utm_medium=email&utm_campaign=server-trial" target="safe"><img src="http://www.safe.com/inc/images/mailouts/fme72.png" width="57" height="40" alt="FME"/></a></td>
                    </tr>

                    <tr>
                      <td align="center"  bgcolor="#FFFFFF" style="background-color: #FFFFFF; padding-bottom:5px;  font-size: 14px; line-height: 20px; font-family:Arial, sans-serif; color: #4b4b4b;"></td>
                    </tr>
                    <tr>
                      <td align="left" class="container-padding" bgcolor="#FFFFFF" style="background-color: #FFFFFF; padding-top:15px; padding-bottom:15px; padding-left: 30px; padding-right: 30px; font-size: 18px; line-height: 24px; font-family:Arial, sans-serif; color: #4b4b4b; mso-line-height-rule:exactly;">

        FME Server evaluation password change request has failed for user '$(user_account)'. <br><br>

        Reason is '@Value(message)'.

                                    <!--END ONE COLUMN-->

                     <!--ONE COLUMN-->
                     <tr>
        			<td style="font-size: 14px; line-height: 20px; font-family: Arial, sans-serif; color: #4b4b4b; text-align: center;"><br>
                      <br>
                    <a href="https://www.safe.com/training/?utm_source=safe&utm_medium=email&utm_campaign=server-trial" style="color:#4b4b4b;text-decoration:none;" target="_blank">Free Training</a> &nbsp;|&nbsp; <a href="https://knowledge.safe.com/questions/index.html?utm_source=safe&utm_medium=email&utm_campaign=server-trial" style="color:#4b4b4b;text-decoration:none;" target="_blank">Q&amp;A Forum</a>&nbsp; | &nbsp;<a href="https://knowledge.safe.com?utm_source=safe&utm_medium=email&utm_campaign=server-trial" style="color:#4b4b4b;text-decoration:none;" target="_blank">Knowledge Base</a></td>
        		</tr>
        		<tr>
        			<td style="font-size: 12px; line-height: 20px; font-family: Arial, sans-serif; color: #4b4b4b; text-align: center;"><br>
        		  Safe Software Inc. Suite 2017, 7445 132nd Street, Surrey, BC Canada V3W 1J8 - <a href="https://www.safe.com/privacy/" style="color:#4b4b4b;text-decoration:none;" title="Legal Info" target="_blank">Privacy Policy</a></td>
        		</tr>
                    <tr>
                      <td align="left" class="container-padding" bgcolor="#eeeeee" style="background-color: #eeeeee; padding-top: 20px; padding-bottom: 15px; padding-left: 0px; padding-right: 0px; font-size: 12px; line-height: 20px; font-family: Arial, sans-serif; color: #4b4b4b; text-align: center;"><p><a href="http://www.safe.com?utm_source=safe&utm_medium=email&utm_campaign=server-trial" target="safe"><img src="http://www.safe.com/inc/images/mailouts/safe-logo-100x41.png" width="100" height="41" alt="Safe Software" style="padding-top:5px; padding-bottom:5px;" /></a>
                      </p>

                      </td>
                    </tr>
                      <!--END ONE COLUMN-->


                      <!--Footer. Only replace URL and Alt Tags-->
                    <!--Dislcaimer Starts-->
                    <!--Disclaimer Ends-->
        </tbody></table></td></tr>

            <!--/600px container -->
        <!--/100% wrapper-->
        </tbody></table></body>
        </html>
    -> HTML (writer HTML_1)

Bookmark: Build Roles
Note: remove user: role
StringReplacer
    FIND_TEXT = "user:[^"]*"(,|])
    NO_MATCH = _FME_NO_OP_
    SRC_ATTRS = roles
    CASE = NO
    REGEXP = YES
    -> StringReplacer_2
Note: Replace beginning
StringReplacer_2
    FIND_TEXT = ["
    REPLACE_TEXT = &roles=
    NO_MATCH = _FME_NO_OP_
    SRC_ATTRS = roles
    CASE = NO
    REGEXP = NO
    -> StringReplacer_4
Note: replace end
StringReplacer_4
    FIND_TEXT = "]
    NO_MATCH = _FME_NO_OP_
    SRC_ATTRS = roles
    CASE = NO
    REGEXP = NO
    -> StringReplacer_5
Note: setup roles
StringReplacer_5
    FIND_TEXT = ","
    REPLACE_TEXT = &roles=
    NO_MATCH = _FME_NO_OP_
    SRC_ATTRS = roles
    CASE = NO
    REGEXP = NO
    -> StringReplacer_6
Note: Remove possible trailing ","
StringReplacer_6
    FIND_TEXT = ",$
    NO_MATCH = _FME_NO_OP_
    SRC_ATTRS = roles
    CASE = NO
    REGEXP = YES
    -> RemoveOldPWD

Bookmark: Generate New Password
RemoveOldPWD: AttributeRemover
    REMOVE_ATTRS = password
    -> GeneratePassword
GeneratePassword: HTTPCaller
    STATUS_CODE_ATTR = _http_status_code
    TARGET_URL = http://www.sethcardoza.com/api/rest/tools/random_password_generator/type:xml/complexity:alphaNumeric/length:10
    SAVE_FILE = Attribute
    TARGET_ATTR = password_xml
    HTTP_METHOD = GET
    CONNECTION_TIMEOUT_LENGTH = 60
    TARGET_ATTR_ENCODING = auto-detect
    TRANSFER_TIMEOUT_LENGTH = 90
    ERROR_ATTR = _error
    USE_COOKIES = No
    FOLLOW_REDIRECTS = Yes
    VERIFY_SSL_CERTIFICATES = Yes
    RESPONSE_HEADER_LIST_ATTR = _headers
    -> XMLFlattener
XMLFlattener
    ATTRIBUTE_XML = password_xml
    FLATTEN_OPTIONS = <structure separator="." map-empty-elements="yes" matched-prefix="attributes" matched-attributes="yes" cardinality="+{?}" structure-prefix="" child-position-attribute="" except-expression="" ui-mode="basic" matched-ancestor-attributes=""/>
    EMBEDDED_EXPRESSIONS = response
    NEW_ATTRIBUTES = password status length complexity
    XML_SOURCE_TYPE = Attribute with XML document
    FEATURE_TYPES_FORMAT_NAME = XML
    -> SetNewPassword
SetNewPassword: HTTPCaller
    AUTH_NAMED_CONNECTION = donsuper FME Server Eval Machine
    STATUS_CODE_ATTR = _http_status_code
    TARGET_URL = $(Evaluation_Server)/fmerest/v3/security/accounts/$(user_account)
    AUTH_METHOD = Web Connection
    SAVE_FILE = Attribute
    TARGET_ATTR = _response_body
    HTTP_METHOD = PUT
    UPLOAD_TYPE = Specify Upload Body
    CONNECTION_TIMEOUT_LENGTH = 60
    TARGET_ATTR_ENCODING = auto-detect
    UPLOAD_CONTENT_TYPE = URL Encoded (application/x-www-form-urlencoded)
    TRANSFER_TIMEOUT_LENGTH = 90
    ERROR_ATTR = _error
    USE_COOKIES = No
    FOLLOW_REDIRECTS = Yes
    VERIFY_SSL_CERTIFICATES = Yes
    UPLOAD_BODY = email=@Value(email)&enabled=@Value(enabled)&fullName=@Value(fullName)&name=@Value(name)&password=@Value(password)@Value(roles)&type=@Value(type)
    RESPONSE_HEADER_LIST_ATTR = _headers
    -> BuildandSendEmail
    <Rejected> -> HTTPCaller__Rejected_

Bookmark: Email to user via Server
BuildandSendEmail
    PASSWORD = @Value(password)
    EMAIL = @Value(email)
    FULLNAME = @Value(fullName)
    USERNAME = @Value(name)
    Full_Name = @Value(fullName)
    -> SuccessWebPage.

Bookmark: Generate Success Web page
Note: create webpage
SuccessWebPage.: AttributeCreator
    ATTR_TABLE:
      SET_TO html_content = <!DOCTYPE html PUBLIC "-//W3C//DTD XHTML 1.0 Transitional//EN" "http://www.w3.org/TR/xhtml1/DTD/xhtml1-transitional.dtd">
        <html xmlns="http://www.w3.org/1999/xhtml">
        <title>We'd like to give you a 60-Day FME Server Trial</title>
        <head>
        <meta http-equiv="Content-Type" content="text/html; charset=UTF-8">
        <meta name="viewport" content="initial-scale=1.0">
        <!-- So that mobile webkit will display zoomed in -->
        <meta name="format-detection" content="telephone=no">
        <!-- disable auto telephone linking in iOS -->
        <style type="text/css">
        /* Resets: see reset.css for details */


        .ReadMsgBody {
        	width: 100%;
        	background-color: #eeeeee;
        }
        .ExternalClass {
        	width: 100%;
        	background-color: #eeeeee;
        }
        .ExternalClass, .ExternalClass p, .ExternalClass span, .ExternalClass font, .ExternalClass td, .ExternalClass div {
        	line-height: 100%;
        }
        body {
        	-webkit-text-size-adjust: none;
        	-ms-text-size-adjust: none;
        }
        body {
        	margin: 0;
        	padding: 0;
        }
        table {
        	border-spacing: 0;
        }
        table td {
        	border-collapse: collapse;
        }
        .yshortcuts a {
        	border-bottom: none !important;
        }
        ul {
        	list-style-type: disc;
        	padding-left: 30px;
        }
        li {
        	list-style-type: inherit;
        	padding-left: 0px;
        	color: #4b4b4b;
        }

        h1 {
        	font-size:22px; line-height: 22px;
        }

        /* Constrain email width for small screens */
        @media screen and (max-width: 900px) {
        table[class="container"] {
        	width: 95% !important;
        }
        }

        /* Give content more room on mobile */
        @media screen and (max-width: 900px) {
        td[class="container-padding"] {
        	padding-left: 12px !important;
        	padding-right: 12px !important;
        }
        }


        /* Force columns into rows */
            @media only screen and (max-width : 900px) {
        /* force container columns to (horizontal) blocks */
        td[class="force-col"] {
        	display: block;
        	padding-right: 0 !important;/*display: table-footer-group;*/
        }
        table[class="col-2"] {
        	/* unset table align="left/right" */
        	float: none !important;
        	width: 100% !important;
        	/* change left/right padding and margins to top/bottom ones */
        	margin-bottom: 12px;
        	padding-bottom: 12px;
          /*border-bottom: 1px solid #A3ABAD;*/
          display: table-header-group;
        }
        /* removes bottom border for last column/row*/
        table[id="last-col-2"] {
        	border-bottom: none !important;
        	margin-bottom: 0px;
        }
        /* Puts images on top*/
        img[class="col-2-img"] {
        	margin-left: 0px;
        	max-width: 900px;
        }
        </style>
        </head>
        <body style="margin:0; padding:10px 0px 0px 0px;" bgcolor="#eeeeee" leftmargin="0" topmargin="0" marginwidth="0" marginheight="0">
        <!-- 100% wrapper (grey background) -->
        <table border="0" width="88%" height="100%" cellpadding="0" cellspacing="0" bgcolor="#eeeeee">
          <tbody>
            <tr>
              <td align="center" valign="top" bgcolor="#eeeeee" style="background-color: #eeeeee;"><!-- 900px container (white background) -->

                <table border="0" width="900" cellpadding="0" cellspacing="0" class="container" bgcolor="#eeeeee">
                  <tbody>
                    <!--ONE COLUMN-->
                    <tr>
                      <td align="center" class="container-padding" bgcolor="#eeeeee" style="background-color: #eeeeee; padding-top:5px; padding-bottom:15px; padding-left: 30px; padding-right: 30px; font-size: 16px; line-height: 20px; font-family:Arial, sans-serif; color: #4b4b4b;"><a href="http://www.safe.com/fme/fme-server/?utm_source=safe&utm_medium=email&utm_campaign=server-trial" target="safe"><img src="http://www.safe.com/inc/images/mailouts/fme72.png" width="57" height="40" alt="FME"/></a></td>
                    </tr>

                    <tr>
                      <td align="center"  bgcolor="#FFFFFF" style="background-color: #FFFFFF; padding-bottom:5px;  font-size: 14px; line-height: 20px; font-family:Arial, sans-serif; color: #4b4b4b;"></td>
                    </tr>
                    <tr>
                      <td align="left" class="container-padding" bgcolor="#FFFFFF" style="background-color: #FFFFFF; padding-top:15px; padding-bottom:15px; padding-left: 30px; padding-right: 30px; font-size: 18px; line-height: 24px; font-family:Arial, sans-serif; color: #4b4b4b; mso-line-height-rule:exactly;">

        FME Server Evaluation Password has been changed. <br><br>

        Password for account '@Value(name)' successfully changed.  Email with account details has been sent to '@Value(email)'.<br><br>

        Please read email for new account password. <br><br>

                                    <!--END ONE COLUMN-->

                     <!--ONE COLUMN-->
                     <tr>
        			<td style="font-size: 14px; line-height: 20px; font-family: Arial, sans-serif; color: #4b4b4b; text-align: center;"><br>
                      <br>
                    <a href="https://www.safe.com/training/?utm_source=safe&utm_medium=email&utm_campaign=server-trial" style="color:#4b4b4b;text-decoration:none;" target="_blank">Free Training</a> &nbsp;|&nbsp; <a href="https://knowledge.safe.com/questions/index.html?utm_source=safe&utm_medium=email&utm_campaign=server-trial" style="color:#4b4b4b;text-decoration:none;" target="_blank">Q&amp;A Forum</a>&nbsp; | &nbsp;<a href="https://knowledge.safe.com?utm_source=safe&utm_medium=email&utm_campaign=server-trial" style="color:#4b4b4b;text-decoration:none;" target="_blank">Knowledge Base</a></td>
        		</tr>
        		<tr>
        			<td style="font-size: 12px; line-height: 20px; font-family: Arial, sans-serif; color: #4b4b4b; text-align: center;"><br>
        		  Safe Software Inc. Suite 2017, 7445 132nd Street, Surrey, BC Canada V3W 1J8 - <a href="https://www.safe.com/privacy/" style="color:#4b4b4b;text-decoration:none;" title="Legal Info" target="_blank">Privacy Policy</a></td>
        		</tr>
                    <tr>
                      <td align="left" class="container-padding" bgcolor="#eeeeee" style="background-color: #eeeeee; padding-top: 20px; padding-bottom: 15px; padding-left: 0px; padding-right: 0px; font-size: 12px; line-height: 20px; font-family: Arial, sans-serif; color: #4b4b4b; text-align: center;"><p><a href="http://www.safe.com?utm_source=safe&utm_medium=email&utm_campaign=server-trial" target="safe"><img src="http://www.safe.com/inc/images/mailouts/safe-logo-100x41.png" width="100" height="41" alt="Safe Software" style="padding-top:5px; padding-bottom:5px;" /></a>
                      </p>

                      </td>
                    </tr>
                      <!--END ONE COLUMN-->


                      <!--Footer. Only replace URL and Alt Tags-->
                    <!--Dislcaimer Starts-->
                    <!--Disclaimer Ends-->
        </tbody></table></td></tr>

            <!--/600px container -->
        <!--/100% wrapper-->
        </tbody></table></body>
        </html>
    -> HTML (writer HTML_1)

FME custom transformer BuildandSendEmail

Parameters:
- Full_Name = Don Murray2   # Full Name
- USERNAME = @Value(username)   # username
- PASSWORD = @Value(password)   # password
- EMAIL = @Value(email)   # email
- FULLNAME = @Value(fullName)   # fullName

Input (input)
    -> AttributeCreator_3
Output (output)

Bookmark: Build Email Content
AttributeCreator_3
    ATTR_LIST:
      email_body,<!DOCTYPE html PUBLIC "-//W3C//DTD XHTML 1.0 Transitional//EN" "http://www.w3.org/TR/xhtml1/DTD/xhtml1-transitional.dtd">
      <html xmlns="http://www.w3.org/1999/xhtml">
      <title>We'd like to give you a 60-Day FME Server Trial</title>
      <head>
      <meta http-equiv="Content-Type" content="text/html; charset=UTF-8">
      <meta name="viewport" content="initial-scale=1.0">
      <!-- So that mobile webkit will display zoomed in -->
      <meta name="format-detection" content="telephone=no">
      <!-- disable auto telephone linking in iOS -->
      <style type="text/css">
      /* Resets: see reset.css for details */


      .ReadMsgBody {
      	width: 100%;
      	background-color: #eeeeee;
      }
      .ExternalClass {
      	width: 100%;
      	background-color: #eeeeee;
      }
      .ExternalClass, .ExternalClass p, .ExternalClass span, .ExternalClass font, .ExternalClass td, .ExternalClass div {
      	line-height: 100%;
      }
      body {
      	-webkit-text-size-adjust: none;
      	-ms-text-size-adjust: none;
      }
      body {
      	margin: 0;
      	padding: 0;
      }
      table {
      	border-spacing: 0;
      }
      table td {
      	border-collapse: collapse;
      }
      .yshortcuts a {
      	border-bottom: none !important;
      }
      ul {
      	list-style-type: disc;
      	padding-left: 30px;
      }
      li {
      	list-style-type: inherit;
      	padding-left: 0px;
      	color: #4b4b4b;
      }

      h1 {
      	font-size:22px; line-height: 22px;
      }

      /* Constrain email width for small screens */
      @media screen and (max-width: 600px) {
      table[class="container"] {
      	width: 95% !important;
      }
      }

      /* Give content more room on mobile */
      @media screen and (max-width: 480px) {
      td[class="container-padding"] {
      	padding-left: 12px !important;
      	padding-right: 12px !important;
      }
      }


      /* Force columns into rows */
          @media only screen and (max-width : 600px) {
      /* force container columns to (horizontal) blocks */
      td[class="force-col"] {
      	display: block;
      	padding-right: 0 !important;/*display: table-footer-group;*/
      }
      table[class="col-2"] {
      	/* unset table align="left/right" */
      	float: none !important;
      	width: 100% !important;
      	/* change left/right padding and margins to top/bottom ones */
      	margin-bottom: 12px;
      	padding-bottom: 12px;
        /*border-bottom: 1px solid #A3ABAD;*/
        display: table-header-group;
      }
      /* removes bottom border for last column/row*/
      table[id="last-col-2"] {
      	border-bottom: none !important;
      	margin-bottom: 0px;
      }
      /* Puts images on top*/
      img[class="col-2-img"] {
      	margin-left: 0px;
      	max-width: 255px;
      }
      </style>
      </head>
      <body style="margin:0; padding:10px 0px 0px 0px;" bgcolor="#eeeeee" leftmargin="0" topmargin="0" marginwidth="0" marginheight="0">
      <!-- 100% wrapper (grey background) -->
      <table border="0" width="88%" height="100%" cellpadding="0" cellspacing="0" bgcolor="#eeeeee">
        <tbody>
          <tr>
            <td align="center" valign="top" bgcolor="#eeeeee" style="background-color: #eeeeee;"><!-- 600px container (white background) -->

              <table border="0" width="600" cellpadding="0" cellspacing="0" class="container" bgcolor="#eeeeee">
                <tbody>
                  <!--ONE COLUMN-->
                  <tr>
                    <td align="center" class="container-padding" bgcolor="#eeeeee" style="background-color: #eeeeee; padding-top:5px; padding-bottom:15px; padding-left: 30px; padding-right: 30px; font-size: 16px; line-height: 20px; font-family:Arial, sans-serif; color: #4b4b4b;"><a href="http://www.safe.com/fme/fme-server/?utm_source=safe&utm_medium=email&utm_campaign=server-trial" target="safe"><img src="http://www.safe.com/inc/images/mailouts/fme72.png" width="57" height="40" alt="FME"/></a></td>
                  </tr>

                  <tr>
                    <td align="center"  bgcolor="#FFFFFF" style="background-color: #FFFFFF; padding-bottom:5px;  font-size: 14px; line-height: 20px; font-family:Arial, sans-serif; color: #4b4b4b;"></td>
                  </tr>
                  <tr>
                    <td align="left" class="container-padding" bgcolor="#FFFFFF" style="background-color: #FFFFFF; padding-top:15px; padding-bottom:15px; padding-left: 30px; padding-right: 30px; font-size: 18px; line-height: 24px; font-family:Arial, sans-serif; color: #4b4b4b; mso-line-height-rule:exactly;">

      Dear $(Full_Name),<br><br>

      Thanks for evaluating FME Server.  We really appreciate it and are here to answer any questions
      that you may have.<br><br>

      We have reset the password for account '@Value(username)'.

      <br><br>
      Your credentials are below.  We encourage you to change your password immediately.
      		<ul>
      			<li>Username: @Value(username)</li>
      			<li>Password: @Value(password)</li>
      		</ul>


      Warm Regards,<br><br>


      Your friendly Safer
                    <br><br>

                                  <!--END ONE COLUMN-->

                   <!--ONE COLUMN-->
                   <tr>
      			<td style="font-size: 14px; line-height: 20px; font-family: Arial, sans-serif; color: #4b4b4b; text-align: center;"><br>
                    <br>
                  <a href="https://www.safe.com/training/?utm_source=safe&utm_medium=email&utm_campaign=server-trial" style="color:#4b4b4b;text-decoration:none;" target="_blank">Free Training</a> &nbsp;|&nbsp; <a href="https://knowledge.safe.com/questions/index.html?utm_source=safe&utm_medium=email&utm_campaign=server-trial" style="color:#4b4b4b;text-decoration:none;" target="_blank">Q&amp;A Forum</a>&nbsp; | &nbsp;<a href="https://knowledge.safe.com?utm_source=safe&utm_medium=email&utm_campaign=server-trial" style="color:#4b4b4b;text-decoration:none;" target="_blank">Knowledge Base</a></td>
      		</tr>
      		<tr>
      			<td style="font-size: 12px; line-height: 20px; font-family: Arial, sans-serif; color: #4b4b4b; text-align: center;"><br>
      		  Safe Software Inc. Suite 2017, 7445 132nd Street, Surrey, BC Canada V3W 1J8 - <a href="https://www.safe.com/privacy/" style="color:#4b4b4b;text-decoration:none;" title="Legal Info" target="_blank">Privacy Policy</a></td>
      		</tr>
                  <tr>
                    <td align="left" class="container-padding" bgcolor="#eeeeee" style="background-color: #eeeeee; padding-top: 20px; padding-bottom: 15px; padding-left: 0px; padding-right: 0px; font-size: 12px; line-height: 20px; font-family: Arial, sans-serif; color: #4b4b4b; text-align: center;"><p><a href="http://www.safe.com?utm_source=safe&utm_medium=email&utm_campaign=server-trial" target="safe"><img src="http://www.safe.com/inc/images/mailouts/safe-logo-100x41.png" width="100" height="41" alt="Safe Software" style="padding-top:5px; padding-bottom:5px;" /></a>
                    </p>

                    </td>
                  </tr>
                    <!--END ONE COLUMN-->


                    <!--Footer. Only replace URL and Alt Tags-->
                  <!--Dislcaimer Starts-->
                  <!--Disclaimer Ends-->
      </tbody></table></td></tr>

          <!--/600px container -->
      <!--/100% wrapper-->
      </tbody></table></body>
      </html>
    -> JSONTemplater [ROOT]
JSONTemplater
    RESULT_ATTRIBUTE = emailNotificationMessage
    VISIBLE_QUERY_VALIDATE = Yes
    ROOT_QUERY_EXPR:
      { "email_to" : fme:get-attribute("email") ,
        "email_subject" : "Your FME Server Trial password has been reset.",
        "subscriber_content" : fme:get-attribute("email_body")
      }
    -> FMEServerNotifier_2

Bookmark: Send Email data to the Topic
FMEServerNotifier_2
    BODY = @Value(emailNotificationMessage)
    SERVER_CONNECTION = dcm bluesky
    TOPIC = hostedEvaluation.signupEmail
    -> FMEServerEmailGenerator_OUTPUT
    -> Output (output)
    <REJECTED> -> Terminator
FMEServerEmailGenerator_OUTPUT: Logger [off]
    MAXCOORDS = 20
    MAXFEATS = 20
    MESSAGE = Feature is:
Terminator
    MESSAGE = Could not notify the user mailer topic

Bookmark: Email example to incorporate later.
Note: This work space simply sends an email to the user specified in the JSON. / This workspace lives on the SERVER. / The email has a simple link to a workspace that is run. The link has the uuid as a query parameter in the url. This is used to get the original request and process it this time with a longer license.
Note: Here is what the link in the email looks like / https://bluesky-safe-software.fmecloud.com/fmedatastreaming/FMELicense.public/4.SERVER-LicenseGenerationToS3.fmw?code=29d80164-1484-11e5-9346-a45e60c71a7b
